----------------------------------------------------------------------------
--Copyright (c) 2016 All rights reserved by
--
--EMC Corporation
--Hopkinton, MA 01748 USA
--
--This software is furnished under a license and may be used and copied
--inclusion of the above copyright notice. This software or any other
--only in accordance with the terms of such license and with the
--copies thereof may not be provided or otherwise made available to any
--other person. No title to and ownership of the software is hereby
--transferred.
--
--The information in this software is subject to change without notice
--and should not be construed as a commitment by EMC Corporation.
--
--EMC Corporation assumes no responsibility for the use or reliability
--of this software.
--
------------------------------------------------------------------------------
--      SRM-ALERTS-MIB 1.10
--              History:
--      1.10    27/05/2016 Creation.
--
--  This MIB should be used by external trap receivers for receiving SRM Alerts as traps.
------------------------------------------------------------------------------

SRM-ALERTS-MIB DEFINITIONS ::= BEGIN
IMPORTS
        OBJECT-TYPE
                FROM RFC-1212
        enterprises
                FROM RFC1155-SMI
        TRAP-TYPE
                FROM RFC-1215;

-- Type Definitions

watch4net OBJECT IDENTIFIER ::= { enterprises 11970 }
alerting OBJECT IDENTIFIER ::= { watch4net 1 }
alertEvent OBJECT IDENTIFIER ::= { alerting 1 }
alertEventTrap OBJECT IDENTIFIER ::= { alertEvent 2 }

-- Objects definitions

device  OBJECT-TYPE
        SYNTAX OCTET STRING (SIZE(0..64))
        ACCESS  read-only
        STATUS  mandatory
        DESCRIPTION
                "The device that the alert occurred on."
        ::= { alertEventTrap  0 }

devtype OBJECT-TYPE
        SYNTAX OCTET STRING (SIZE(0..64))
        ACCESS  read-only
        STATUS  mandatory
        DESCRIPTION
                "The device type that the alert occurred on."
        ::= { alertEventTrap  1 }


part    OBJECT-TYPE
        SYNTAX OCTET STRING (SIZE(0..64))
        ACCESS  read-only
        STATUS  mandatory
        DESCRIPTION
                "The part that the alert occurred on."
        ::= { alertEventTrap  2 }


parttype    OBJECT-TYPE
            SYNTAX OCTET STRING (SIZE(0..64))
            ACCESS  read-only
            STATUS  mandatory
            DESCRIPTION
                    "The part type that the alert occurred on."
            ::= { alertEventTrap  3 }


sourceeventtype OBJECT-TYPE
                SYNTAX OCTET STRING (SIZE(0..64))
                ACCESS  read-only
                STATUS  mandatory
                DESCRIPTION
                        "The event type from the source of the alert."
                ::= { alertEventTrap  4 }


value   OBJECT-TYPE
        SYNTAX OCTET STRING (SIZE(0..64))
        ACCESS  read-only
        STATUS  mandatory
        DESCRIPTION
                "The value of the metric or attribute that caused the alert."
        ::= { alertEventTrap  5 }

severity    OBJECT-TYPE
            SYNTAX OCTET STRING (SIZE(0..64))
            ACCESS  read-only
            STATUS  mandatory
            DESCRIPTION
                    "The severity of the alert - CRITICAL(1), MAJOR(2), MINOR(3), UNKNOWN(4), INFORMATIONAL(5)."
            ::= { alertEventTrap  6 }


fullmsg OBJECT-TYPE
        SYNTAX OCTET STRING
        ACCESS  read-only
        STATUS  mandatory
        DESCRIPTION
                "A message used to describe more information about the alert."
        ::= { alertEventTrap  7 }

source  OBJECT-TYPE
        SYNTAX OCTET STRING (SIZE(0..64))
        ACCESS  read-only
        STATUS  mandatory
        DESCRIPTION
                "The source of the alert."
        ::= { alertEventTrap  8 }

openedat    OBJECT-TYPE
            SYNTAX OCTET STRING (SIZE(0..64))
            ACCESS  read-only
            STATUS  mandatory
            DESCRIPTION
                    "The date and time when the alert first occurs."
            ::= { alertEventTrap  9 }

category    OBJECT-TYPE
            SYNTAX OCTET STRING (SIZE(0..64))
            ACCESS  read-only
            STATUS  mandatory
            DESCRIPTION
                    "The category of the alert."
            ::= { alertEventTrap  10 }

sourceip    OBJECT-TYPE
            SYNTAX OCTET STRING (SIZE(0..64))
            ACCESS  read-only
            STATUS  mandatory
            DESCRIPTION
                    "The IP of the source of the alert."
            ::= { alertEventTrap  11 }

sourcedomainname    OBJECT-TYPE
                    SYNTAX OCTET STRING (SIZE(0..64))
                    ACCESS  read-only
                    STATUS  mandatory
                    DESCRIPTION
                            "The domain name of the source of the alert."
                    ::= { alertEventTrap  12 }


userdefined1    OBJECT-TYPE
                SYNTAX OCTET STRING
                ACCESS  read-only
                STATUS  mandatory
                DESCRIPTION
                        "A custom field that can be modified by the system administrator."
                ::= { alertEventTrap  13 }

userdefined2    OBJECT-TYPE
                SYNTAX OCTET STRING
                ACCESS  read-only
                STATUS  mandatory
                DESCRIPTION
                        "A custom field that can be modified by the system administrator."
                ::= { alertEventTrap  14 }

userdefined3    OBJECT-TYPE
                SYNTAX OCTET STRING
                ACCESS  read-only
                STATUS  mandatory
                DESCRIPTION
                        "A custom field that can be modified by the system administrator."
                ::= { alertEventTrap  15 }

userdefined4    OBJECT-TYPE
                SYNTAX OCTET STRING
                ACCESS  read-only
                STATUS  mandatory
                DESCRIPTION
                        "A custom field that can be modified by the system administrator."
                ::= { alertEventTrap  16 }

userdefined5    OBJECT-TYPE
                SYNTAX OCTET STRING
                ACCESS  read-only
                STATUS  mandatory
                DESCRIPTION
                        "A custom field that can be modified by the system administrator."
                ::= { alertEventTrap  17 }

userdefined6    OBJECT-TYPE
                SYNTAX OCTET STRING
                ACCESS  read-only
                STATUS  mandatory
                DESCRIPTION
                        "A custom field that can be modified by the system administrator."
                ::= { alertEventTrap  18 }


eventname   OBJECT-TYPE
            SYNTAX OCTET STRING (SIZE(0..64))
            ACCESS  read-only
            STATUS  mandatory
            DESCRIPTION
                    "The name of the alert."
            ::= { alertEventTrap  19 }


eventstate  OBJECT-TYPE
            SYNTAX OCTET STRING (SIZE(0..64))
            ACCESS  read-only
            STATUS  mandatory
            DESCRIPTION
                    "The mandatory state of the alert, (ACTIVE or INACTIVE)."
            ::= { alertEventTrap  20 }


eventdisplayname    OBJECT-TYPE
                    SYNTAX OCTET STRING (SIZE(0..64))
                    ACCESS  read-only
                    STATUS  mandatory
                    DESCRIPTION
                            "The display-ready name of the alert."
                    ::= { alertEventTrap  21 }


systemdefined1  OBJECT-TYPE
                SYNTAX OCTET STRING
                ACCESS  read-only
                STATUS  mandatory
                DESCRIPTION
                        "A custom field that is reserved for M&R Platform and SolutionPack use."
                ::= { alertEventTrap  22 }

systemdefined2  OBJECT-TYPE
                SYNTAX OCTET STRING
                ACCESS  read-only
                STATUS  mandatory
                DESCRIPTION
                        "A custom field that is reserved for M&R Platform and SolutionPack use."
                ::= { alertEventTrap  23 }

systemdefined3  OBJECT-TYPE
                SYNTAX OCTET STRING
                ACCESS  read-only
                STATUS  mandatory
                DESCRIPTION
                        "A custom field that is reserved for M&R Platform and SolutionPack use."
                ::= { alertEventTrap  24 }

systemdefined4  OBJECT-TYPE
                SYNTAX OCTET STRING
                ACCESS  read-only
                STATUS  mandatory
                DESCRIPTION
                        "A custom field that is reserved for M&R Platform and SolutionPack use."
                ::= { alertEventTrap  25 }

systemdefined5  OBJECT-TYPE
                SYNTAX OCTET STRING
                ACCESS  read-only
                STATUS  mandatory
                DESCRIPTION
                        "A custom field that is reserved for M&R Platform and SolutionPack use."
                ::= { alertEventTrap  26 }


count   OBJECT-TYPE
        SYNTAX OCTET STRING (SIZE(0..64))
        ACCESS  read-only
        STATUS  mandatory
        DESCRIPTION
                "Number of times an alert has occurred."
        ::= { alertEventTrap  27 }


parttypedisplayname    OBJECT-TYPE
                       SYNTAX OCTET STRING (SIZE(0..64))
                       ACCESS  read-only
                       STATUS  mandatory
                       DESCRIPTION
                               "The display-ready part type that the alert occurred on."
                       ::= { alertEventTrap  28 }


partdisplayname OBJECT-TYPE
                SYNTAX OCTET STRING (SIZE(0..64))
                ACCESS  read-only
                STATUS  mandatory
                DESCRIPTION
                        "The display-ready part that the alert occurred on."
                ::= { alertEventTrap  29 }

closedat    OBJECT-TYPE
            SYNTAX OCTET STRING (SIZE(0..64))
            ACCESS  read-only
            STATUS  mandatory
            DESCRIPTION
                    "The date-time when the alert was closed."
            ::= { alertEventTrap  30 }

duration OBJECT-TYPE
         SYNTAX OCTET STRING (SIZE(0..64))
         ACCESS  read-only
         STATUS  mandatory
         DESCRIPTION
                "The duration between when the alert was ACTIVE to INACTIVE."
         ::= { alertEventTrap  31 }

isroot  OBJECT-TYPE
        SYNTAX OCTET STRING (SIZE(0..64))
        ACCESS  read-only
        STATUS  mandatory
        DESCRIPTION
                "A (1) value indicates this alert is has no known deeper underlying cause."
        ::= { alertEventTrap  32 }

isproblem   OBJECT-TYPE
            SYNTAX OCTET STRING (SIZE(0..64))
            ACCESS  read-only
            STATUS  mandatory
            DESCRIPTION
                    "A (1) value indicates this alert was discovered via Codebook Correlation."
            ::= { alertEventTrap  33 }

eventtext   OBJECT-TYPE
            SYNTAX OCTET STRING
            ACCESS  read-only
            STATUS  mandatory
            DESCRIPTION
                    "A description of the alert"
            ::= { alertEventTrap  34 }

impact  OBJECT-TYPE
        SYNTAX OCTET STRING (SIZE(0..64))
        ACCESS  read-only
        STATUS  mandatory
        DESCRIPTION
                "The impact of the alert."
        ::= { alertEventTrap  35}

certainty   OBJECT-TYPE
            SYNTAX OCTET STRING (SIZE(0..64))
            ACCESS  read-only
            STATUS  mandatory
            DESCRIPTION
                    "The certainty of the alert."
            ::= { alertEventTrap  36 }

eventtype   OBJECT-TYPE
            SYNTAX OCTET STRING (SIZE(0..64))
            ACCESS  read-only
            STATUS  mandatory
            DESCRIPTION
                    "The type of event, (MOMENTARY, DURABLE)."
            ::= { alertEventTrap  37 }


active  OBJECT-TYPE
        SYNTAX OCTET STRING (SIZE(0..64))
        ACCESS  read-only
        STATUS  mandatory
        DESCRIPTION
                "A (1) value indicates this alert is currently active on the system."
        ::= { alertEventTrap  38 }

lastchangedat   OBJECT-TYPE
                SYNTAX OCTET STRING (SIZE(0..64))
                ACCESS  read-only
                STATUS  mandatory
                DESCRIPTION
                        "The date and time when an alert was last updated."
                ::= { alertEventTrap  39 }

acknowledged OBJECT-TYPE
             SYNTAX OCTET STRING (SIZE(0..64))
             ACCESS  read-only
             STATUS  mandatory
             DESCRIPTION
                     "A (1) value indicates that the alert has been acknowledged by a user."
             ::= { alertEventTrap  40 }

inmaintenance   OBJECT-TYPE
                SYNTAX OCTET STRING (SIZE(0..64))
                ACCESS  read-only
                STATUS  mandatory
                DESCRIPTION
                        "A (1) value indicates the device this alert occurs on is currently undergoing maintenance"
                ::= { alertEventTrap  41 }

troubleticketid OBJECT-TYPE
                SYNTAX OCTET STRING (SIZE(0..64))
                ACCESS  read-only
                STATUS  mandatory
                DESCRIPTION
                        "The ID of this alerting in an external ticket management system."
                ::= { alertEventTrap  42 }

owner   OBJECT-TYPE
        SYNTAX OCTET STRING (SIZE(0..64))
        ACCESS  read-only
        STATUS  mandatory
        DESCRIPTION
                "The current owner of the alert."
        ::= { alertEventTrap  43 }

userdefined7    OBJECT-TYPE
                SYNTAX OCTET STRING
                ACCESS  read-only
                STATUS  mandatory
                DESCRIPTION
                        "A custom field that can be modified by the system administrator."
                ::= { alertEventTrap  44 }

userdefined8    OBJECT-TYPE
                SYNTAX OCTET STRING
                ACCESS  read-only
                STATUS  mandatory
                DESCRIPTION
                        "A custom field that can be modified by the system administrator."
                ::= { alertEventTrap  45 }

userdefined9    OBJECT-TYPE
                SYNTAX OCTET STRING
                ACCESS  read-only
                STATUS  mandatory
                DESCRIPTION
                        "A custom field that can be modified by the system administrator."
                ::= { alertEventTrap  46 }

userdefined10   OBJECT-TYPE
                SYNTAX OCTET STRING
                ACCESS  read-only
                STATUS  mandatory
                DESCRIPTION
                        "A custom field that can be modified by the system administrator."
                ::= { alertEventTrap  47 }

userdefined11   OBJECT-TYPE
                SYNTAX OCTET STRING
                ACCESS  read-only
                STATUS  mandatory
                DESCRIPTION
                        "A custom field that can be modified by the system administrator."
                ::= { alertEventTrap  48 }

userdefined12   OBJECT-TYPE
                SYNTAX OCTET STRING
                ACCESS  read-only
                STATUS  mandatory
                DESCRIPTION
                        "A custom field that can be modified by the system administrator."
                ::= { alertEventTrap  49 }

userdefined13   OBJECT-TYPE
                SYNTAX OCTET STRING
                ACCESS  read-only
                STATUS  mandatory
                DESCRIPTION
                        "A custom field that can be modified by the system administrator."
                ::= { alertEventTrap  50 }

userdefined14   OBJECT-TYPE
                SYNTAX OCTET STRING
                ACCESS  read-only
                STATUS  mandatory
                DESCRIPTION
                        "A custom field that can be modified by the system administrator."
                ::= { alertEventTrap  51 }

userdefined15   OBJECT-TYPE
                SYNTAX OCTET STRING
                ACCESS  read-only
                STATUS  mandatory
                DESCRIPTION
                        "A custom field that can be modified by the system administrator."
                ::= { alertEventTrap  52 }

userdefined16   OBJECT-TYPE
                SYNTAX OCTET STRING
                ACCESS  read-only
                STATUS  mandatory
                DESCRIPTION
                        "A custom field that can be modified by the system administrator."
                ::= { alertEventTrap  53 }

userdefined17   OBJECT-TYPE
                SYNTAX OCTET STRING
                ACCESS  read-only
                STATUS  mandatory
                DESCRIPTION
                        "A custom field that can be modified by the system administrator."
                ::= { alertEventTrap  54 }

userdefined18   OBJECT-TYPE
                SYNTAX OCTET STRING
                ACCESS  read-only
                STATUS  mandatory
                DESCRIPTION
                        "A custom field that can be modified by the system administrator."
                ::= { alertEventTrap  55 }

userdefined19   OBJECT-TYPE
                SYNTAX OCTET STRING
                ACCESS  read-only
                STATUS  mandatory
                DESCRIPTION
                        "A custom field that can be modified by the system administrator."
                ::= { alertEventTrap  56 }

userdefined20   OBJECT-TYPE
                SYNTAX OCTET STRING
                ACCESS  read-only
                STATUS  mandatory
                DESCRIPTION
                        "A custom field that can be modified by the system administrator."
                ::= { alertEventTrap  57 }
 
 

-- Trap Definitions ------------------------------------------------------------
alertEventTrapMessage    TRAP-TYPE
        ENTERPRISE      alertEventTrap
        VARIABLES       {
                        id,
                        name,
                        openedat,
                        count,
                        eventstate,
                        source,
                        parttype,
                        part,
                        eventname,
                        parttypedisplayname,
                        partdisplayname,
                        eventdisplayname,
                        fullmsg,
                        devtype,
                        device,
                        sourceip,
                        sourcedomainname,
                        sourceeventtype,
                        value,
                        active,
                        timestamp,
                        closedat,
                        duration,
                        lastchangedat,
                        isroot,
                        isproblem,
                        acknowledged,
                        eventtype,
                        category,
                        eventtext,
                        severity,
                        impact,
                        certainty,
                        inmaintenance,
                        troubleticketid,
                        owner,
                        systemdefined1,
                        systemdefined2,
                        systemdefined3,
                        systemdefined4,
                        systemdefined5,
                        userdefined1,
                        userdefined2,
                        userdefined3,
                        userdefined4,
                        userdefined5,
                        userdefined6,
                        userdefined7,
                        userdefined8,
                        userdefined9,
                        userdefined10,
                        userdefined11,
                        userdefined12,
                        userdefined13,
                        userdefined14,
                        userdefined15,
                        userdefined16,
                        userdefined17,
                        userdefined18,
                        userdefined19,
                        userdefined20
                        }
            DESCRIPTION
                "Trap for alerts."
            ::= 1

END
